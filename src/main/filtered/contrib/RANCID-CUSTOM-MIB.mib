---
   --- SNMP v1 MIB FILE
   --- RANCID SNMP NOTIFICATIONS
   --- (as implemented for the OpenNMS/RANCID integration project)
   ---
   --- Version 1.3 (2009 05 08)
   ---
   --- Please note: as a member of the OpenNMS/RANCID project team, I
   --- implemented the enclosed MIB definitions under my own private
   --- enterprise number officially assigned by IANA.
   ---
   --- If you need any information or want to modify or extend this MIB,
   ---
   ---		    *** PLEASE *** PLEASE *** PLEASE ***
   ---
   --- contact me at the following address: <iana-pen-contact@rionero.com>.
   ---
   ---						Thank you.
   ---						Rocco "rock" RIONERO
   ---
   ---
   --- History of changes:
   ---
   ---	1.3	- added the following two specific traps:
   ---
   ---			"rancidTrapGroupProcessingStarted"
   ---			"rancidTrapGroupProcessingCompleted"
   ---
   ---
   ---	1.2	- added the following three specific traps (contributed by
   ---		  Philippe Guillebert <philippe.guillebert@bull.net>):
   ---
   ---			"rancidTrapNodeAdded"
   ---			"rancidTrapNodeDeleted"
   ---			"rancidTrapConfigurationChanged"
   ---
   ---		  NOTE:	the original trap-names proposed by Philippe were
   ---			changed in conformance to the general MIB naming
   ---			scheme.
   ---
   ---
   ---	1.1	- corrected the descriptions for "rancidTrapGenericFailure"
   ---		  and "rancidFailureMessage"
   ---
   ---
   ---	1.0	- initial release
   ---


   RANCID-CUSTOM-MIB DEFINITIONS ::= BEGIN


   IMPORTS
       OBJECT-TYPE
           FROM RFC-1212
       enterprises
           FROM RFC1155-SMI
       DisplayString
           FROM RFC1213-MIB
       TRAP-TYPE
           FROM RFC-1215;



   ---
   --- Following are pre-requisites placed here to keep this module short
   --- and to avoid importing other not needed private MIBs
   ---

   RIONERO                  OBJECT IDENTIFIER ::= { enterprises 31543 }

   SoftwareApplications     OBJECT IDENTIFIER ::= { RIONERO 1 }

   OpenSource               OBJECT IDENTIFIER ::= { SoftwareApplications 1 }

   customizations           OBJECT IDENTIFIER ::= { OpenSource 2 }



   ---
   --- Here the actual module definitions begin
   ---

   rancidCustomMIB          OBJECT IDENTIFIER ::= { customizations 1 }

   rancidObjects            OBJECT IDENTIFIER ::= { rancidCustomMIB 1 }

   rancidTraps              OBJECT IDENTIFIER ::= { rancidCustomMIB 2 }



   ---
   --- data objects
   ---

   rancidDeviceName OBJECT-TYPE
       SYNTAX      OCTET STRING (SIZE (0..64))
       ACCESS      read-only
       STATUS      current
       DESCRIPTION "The name of a rancid's managed device."
       ::= { rancidObjects 1 }


   rancidDeviceType OBJECT-TYPE
       SYNTAX      OCTET STRING (SIZE (0..32))
       ACCESS      read-only
       STATUS      current
       DESCRIPTION "The name of a rancid's deviceType."
       ::= { rancidObjects 2 }


   rancidGroupName OBJECT-TYPE
       SYNTAX      OCTET STRING (SIZE (0..64))
       ACCESS      read-only
       STATUS      current
       DESCRIPTION "The name of a rancid's group of managed devices."
       ::= { rancidObjects 3 }


   rancidFailureMessage OBJECT-TYPE
       SYNTAX      DisplayString
       ACCESS      read-only
       STATUS      current
       DESCRIPTION "A string describing a failure condition for which
       		   is not defined a more specific trap."
       ::= { rancidObjects 4 }




   --
   -- notifications, i.e., traps
   --

   rancidTrapGenericFailure TRAP-TYPE
       ENTERPRISE  rancidTraps
       VARIABLES   { rancidFailureMessage }
       DESCRIPTION "This trap is sent each time rancid needs to notify a
                   failure condition for which is not defined a more
                   specific trap."
   ::= 1


   rancidTrapDownloadSuccess TRAP-TYPE
       ENTERPRISE  rancidTraps
       VARIABLES   { rancidGroupName, rancidDeviceName }
       DESCRIPTION "This trap is sent each time rancid successfully downloads
     	 	   the configuration from a device."
   ::= 2


   rancidTrapDownloadFailure TRAP-TYPE
       ENTERPRISE  rancidTraps
       VARIABLES   { rancidGroupName, rancidDeviceName }
       DESCRIPTION "This trap is sent each time rancid fails to download the
       		   configuration from a device."
   ::= 3


   rancidTrapGroupLocked TRAP-TYPE
       ENTERPRISE  rancidTraps
       VARIABLES   { rancidGroupName }
       DESCRIPTION "This trap is sent each time rancid is not able to process
                   a group of devices due to the existence of a group's lock
                   file."
   ::= 4


   rancidTrapNodeAdded TRAP-TYPE
       ENTERPRISE  rancidTraps
       VARIABLES   { rancidGroupName, rancidDeviceName }
       DESCRIPTION "This trap is sent each time rancid detects that a new
       		   device was added to a group's configuration file."

   ::= 5


   rancidTrapNodeDeleted TRAP-TYPE
       ENTERPRISE  rancidTraps
       VARIABLES   { rancidGroupName, rancidDeviceName }
       DESCRIPTION "This trap is sent each time rancid detects that a device
       		   was deleted from a group's configuration file."
   ::= 6


   rancidTrapConfigurationChanged TRAP-TYPE
       ENTERPRISE  rancidTraps
       VARIABLES   { rancidGroupName, rancidDeviceName }
       DESCRIPTION "This trap is sent each time rancid detects that the
	            configuration of a device has changed."
   ::= 7


   rancidTrapGroupProcessingStarted TRAP-TYPE
       ENTERPRISE  rancidTraps
       VARIABLES   { rancidGroupName }
       DESCRIPTION "This trap is sent each time rancid acquires a group's
       		   lockfile and starts processing the corresponding devices."
   ::= 8


   rancidTrapGroupProcessingCompleted TRAP-TYPE
       ENTERPRISE  rancidTraps
       VARIABLES   { rancidGroupName }
       DESCRIPTION "This trap is sent each time rancid releases a group's
       		   lockfile after having processed the corresponding devices."
   ::= 9


   END
