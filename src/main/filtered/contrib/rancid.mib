--
-- RANCID-MIB       module definition
--

-- Copyright (C) 2008-2009 by Rocco Rionero.


-- Version 1.0 - 2009-03-25: 	The main purpose of this first version of
--				the RANCID MIB is to instrument the values
--				passed in the traps sent by rancid.


RANCID-MIB DEFINITIONS ::= BEGIN
IMPORTS
   OBJECT-TYPE FROM RFC-1212
   DisplayString FROM RFC1213-MIB
   enterprises FROM RFC1155-SMI
   TRAP-TYPE FROM RFC-1215
   TimeTicks FROM RFC1155-SMI
   IpAddress FROM RFC1155-SMI;

rionero				OBJECT IDENTIFIER
							::= { enterprises 31543 }

rancid				OBJECT IDENTIFIER
							::= { rionero 1234 }

rancid-traps			OBJECT IDENTIFIER
							::= { rancid 1 }

rancid-data				OBJECT IDENTIFIER
							::= { rancid 20 }

rancid-entry			OBJECT IDENTIFIER
							::= { rancid-data 1 }

rancid-device-name		OBJECT-TYPE
	SYNTAX		DisplayString
	ACCESS		read-only
	STATUS		mandatory
	DESCRIPTION 	"This is the Rancid device name . Each
			entry in rancid has a unique identifier
			under a specified Rancid group."
	::= { rancid-entry 1 }

rancid-group			OBJECT-TYPE
	SYNTAX		DisplayString
	ACCESS		read-only
	STATUS		mandatory
	DESCRIPTION 	"This is the Rancid group."
	::= { rancid-entry 2 }

rancid-device-type		OBJECT-TYPE
	SYNTAX		DisplayString
	ACCESS		read-only
	STATUS		mandatory
	DESCRIPTION 	"This is the device type category."
	::= { rancid-entry 3 }

rancid-description		OBJECT-TYPE
	SYNTAX		DisplayString
	ACCESS		read-only
	STATUS		mandatory
	DESCRIPTION 	"This is a generic description."
	::= { rancid-entry 4 }

				
-- Trap definitions

rancid-Generic-Trap		TRAP-TYPE
	ENTERPRISE rancid-traps
	VARIABLES {
		rancid-description
	}
	DESCRIPTION 
	"This is the definition of the generic rancid trap sent from the
	rancid-run process."
	::= 1

rancid-downloadSuccessTrap	TRAP-TYPE
	ENTERPRISE rancid-traps
	VARIABLES {
		rancid-device-name,
		rancid-group
	}
	DESCRIPTION
		"This trap is sent after a success in configuration download ."
	::= 2

rancid-downloadFailureTrap	TRAP-TYPE
	ENTERPRISE rancid-traps
	VARIABLES {
		rancid-device-name,
		rancid-group
	}
	DESCRIPTION
		"This trap is sent after a failure in configuration download."
	::= 3

END
